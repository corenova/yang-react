module yang-react-dom {
  namespace "urn:ietf:params:xml:ns:yang:yang-react";
  prefix dom;
  yang-version 1.1;

  import yang-meta-types { prefix meta; }

  organization
    "Corenova Technologies, Inc.";
  contact
    "Peter K. Lee <peter@corenova.com>";
  reference
    "https://facebook.github.io/react";

  typedef selector {
    type string;
  }
  
  grouping attributes-list {
    leaf name {
      type meta:meta-identifier;
      mandatory true;
    }
    leaf value;
  }
  grouping element {
    leaf name {
      type meta:meta-identifier;
      mandatory true;
    }
    uses dom:attributes-list;
    list node {
      uses dom:element;
    }
  }

  rpc render {
    input {
      container element {
        uses dom:element;
      }
      leaf target {
        type dom:selector;
      }
    }
  }
}
